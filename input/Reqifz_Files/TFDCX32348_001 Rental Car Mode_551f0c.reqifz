# Json2ReqIF Transformation

# Specification: 001 Rental Car Mode
- JDA Snapshot Date: 2025-06-25 09:19:59

## TFDCX32348-7472: Rental Car Mode (Heading)

## TFDCX32348-7473: History (Heading)

### TFDCX32348-7793: History (Information)
| Version | Date | Name | Description of change | SRD Baseline |
| --- | --- | --- | --- | --- |
| 1.0 (38xD) | 29/Aug/2022 | ttakaba | [SYS][38xD][HMI] Rent-A-Car Mode (1688062) First release. | BL_20220917_01 |
| 1.1 (12.3FDC) | 29/Jan/2025 | ttakaba | TFDCX32348-34138 [SYS][12.3FDC][APP][Rental car] Rental Car Mode Display No logic update from 38xD. | BL_20250129_01 |

## TFDCX32348-7474: Overview (Heading)

### TFDCX32348-7795: This feature judges rental car mode. ... (Information)
This feature judges rental car mode. If rental car mode is established after IG and ACC are both OFF for specified duration.
If rental car mode is active, ODO and CLOCK will be displayed on the TFT.
Enabling/disabling rental car mode and the mode establishment time can be configured by NVM_RentalCarModeTM.

## TFDCX32348-63037: Reference Documents (Heading)

### TFDCX32348-63038: Reference documents (Information)
MET-M_RNTMODE-CSTD-0-01-B-C0

## TFDCX32348-7475: Input Requirements (Heading)

### TFDCX32348-7797: InternalSignal - AppMode (System Interface)
- Verification Criteria: Verify by code review
- Verification Method: Code/Design Review
- Verification Owner: SW
- System Requirement State: Approved
- Primary Discipline: SW
- ASIL Rating: QM

### TFDCX32348-7799: InternalSignal - ACCStatus (System Interface)
- Verification Criteria: Verify by code review
- Verification Method: Code/Design Review
- Verification Owner: SW
- System Requirement State: Approved
- Primary Discipline: SW
- ASIL Rating: QM

### TFDCX32348-7801: InternalSignal - IgnMode (System Interface)
- Verification Criteria: Verify by code review
- Verification Method: Code/Design Review
- Verification Owner: SW
- System Requirement State: Approved
- Primary Discipline: SW
- ASIL Rating: QM

### TFDCX32348-7803: CANSignal - PARK_S (Message Label: SCN1S02) (System Interface)
- Verification Criteria: Verify by code review
- Verification Method: Code/Design Review
- Verification Owner: SW
- System Requirement State: Approved
- Primary Discipline: SW
- ASIL Rating: QM

### TFDCX32348-7805: CANSignal - DCTY (Message Label: BDB1S01) (System Interface)
- Verification Criteria: Verify by code review
- Verification Method: Code/Design Review
- Verification Owner: SW
- System Requirement State: Approved
- Primary Discipline: SW
- ASIL Rating: QM

## TFDCX32348-7476: Output Requirements (Heading)

### TFDCX32348-7808: InternalSignal - RentalCarMode (System Interface)
InternalSignal - RentalCarMode
Meaning: This parameter indicates the status of Rental Car Mode.
Type: Boolean
Range: FALSE, TRUE (Rental Car mode is ON)
- Verification Criteria: Verify by code review
- Verification Method: Code/Design Review
- Verification Owner: SW
- System Requirement State: Approved
- Primary Discipline: SW
- ASIL Rating: QM

## TFDCX32348-7477: NVM Requirements (Heading)

### TFDCX32348-7810: NVM Parameter - NVM_RentalCarModeTM (System Interface)
NVM Parameter - NVM_RentalCarModeTM (Read only)
Meaning: This parameter configures the time duration of the rental car mode.
Type: UINT8
Range: 00h = 30 sec, 01h = 60 sec, 02h = 600 sec, 03h = 0 sec [No available reltal car mode]), 04h-FFh = Not used.
- Verification Criteria: Verify by code review
- Verification Method: Code/Design Review
- Verification Owner: SW
- System Requirement State: Approved
- Primary Discipline: SW
- ASIL Rating: QM

## TFDCX32348-7478: Performance Requirements (Heading)

### TFDCX32348-7812: Rental Car Mode Judgement (Heading)

#### TFDCX32348-11301: PARK_S Status Judgement (System Requirement)
PARK_S Status Judgement
| # | Input |  | Output |
| --- | --- | --- | --- |
| # | CANSignal Status - PARK_S | CANSignal - PARK_S | Internal Parameter - PARK_S_Status |
| 1 | Never Received or Communication Failure | X | FALSE |
| 2 | Received and Normal | 010010b or 010011b or 010100b or 010101b or 010111b | TRUE |
| 3 | Received and Normal | Other than above | FALSE |
- Verification Criteria: Verify by executing test cases
- Verification Method: System Qualification Test
- Verification Owner: FV
- System Requirement State: Approved
- Primary Discipline: SW
- ASIL Rating: QM

#### TFDCX32348-11303: DCTY Status Judgement (System Requirement)
DCTY Status Judgement
| # | Input |  | Output |
| --- | --- | --- | --- |
| # | CANSignal Status - DCTY | CANSignal - DCTY | Internal Parameter - DCTY_Status |
| 1 | Never Received or Communication Failure | X | FALSE |
| 2 | Received and Normal | 0 | FALSE |
| 3 | Received and Normal | 1 | TRUE |
- Verification Criteria: Verify by executing test cases
- Verification Method: System Qualification Test
- Verification Owner: FV
- System Requirement State: Approved
- Primary Discipline: SW
- ASIL Rating: QM

#### TFDCX32348-11305: Rental Car Mode Timer Processing (System Requirement)
Rental Car Mode Timer Processing
| # | Input |  |  |  |  |  | Output |  | Remarks |
| --- | --- | --- | --- | --- | --- | --- | --- | --- | --- |
| # | InternalSignal - AppMode | InternalSignal - ACCStatus | InternalSignal - IgnMode | Internal Parameter AccIgn_PrevStatus current value (*1) | Internal Parameter - PARK_S_Status | Internal Parameter - DCTY_Status | Internal Parameter AccIgn_PrevStatus | Internal Timer - RentalCarModeTimer | Remarks |
| 1 | (Initialization at CPU reset or wakeup) |  |  |  |  |  | BOTH_OFF | Stop | Initialization |
| 2 | Sleep Mode | X | X | X | X | X | BOTH_OFF | Stop |  |
| 3 | Other than Sleep Mode | ON | X | X | X | X | ANY_ON | Stop | If either IG or ACC is ON, stop rental car mode timer. |
| 4 | Other than Sleep Mode | X | ON | X | X | X | ANY_ON | Stop | If either IG or ACC is ON, stop rental car mode timer. |
| 5 | Other than Sleep Mode | OFF | OFF | ANY_ON | TRUE | X | BOTH_OFF | Stop | Rental car mode exit condition is satisfied at start timing. |
| 6 | Other than Sleep Mode | OFF | OFF | ANY_ON | FALSE | X | BOTH_OFF | Refer to table (2) | Rental car mode start condition is satisfied. |
| 7 | Other than Sleep Mode | OFF | OFF | BOTH_OFF | TRUE | X | BOTH_OFF | Stop | Rental car mode exit condition is satisfied. |
| 8 | Other than Sleep Mode | OFF | OFF | BOTH_OFF | FALSE | FALSE to TRUE | BOTH_OFF | Refer to table (2) | Rental car mode restart condition is satisfied. |
| 9 | Other than Sleep Mode | OFF | OFF | BOTH_OFF | FALSE | other than (FALSE to TRUE) | BOTH_OFF | Count if timer is running | Timer count down. |
(*1) "current value" means the value before processing this table.
- Verification Criteria: Verify by executing test cases
- Verification Method: System Qualification Test
- Verification Owner: FV
- System Requirement State: Approved
- Primary Discipline: SW
- ASIL Rating: QM

#### TFDCX32348-11307 (System Requirement)
Rental Car Mode Timer Processing Table (2)
| # | Input | Output |
| --- | --- | --- |
| # | NVM_RentalCarModeTM | Internal Timer - RentalCarModeTimer |
| 1 | 00h | Start timer with 30 sec (*1) |
| 2 | 01h | Start timer with 60 sec (*1) |
| 3 | 02h | Start timer with 600 sec (*1) |
| 4 | 03h to FFh | Stop |
(*1) Re-start timer if the timer is alerady running.
- Verification Criteria: Verify by executing test cases
- Verification Method: System Qualification Test
- Verification Owner: FV
- System Requirement State: Approved
- Primary Discipline: SW
- ASIL Rating: QM

#### TFDCX32348-11309: Rental Car Mode Final Judgement (System Requirement)
Rental Car Mode Final Judgement
| # | Input | Output |
| --- | --- | --- |
| # | Internal Timer - RentalCarModeTimer | Internal Parameter (output) - RentalCarMode |
| 1 | Running | TRUE |
| 2 | Expired or Stop | FALSE |
- Verification Criteria: Verify by executing test cases
- Verification Method: System Qualification Test
- Verification Owner: FV
- System Requirement State: Approved
- Primary Discipline: SW
- ASIL Rating: QM
