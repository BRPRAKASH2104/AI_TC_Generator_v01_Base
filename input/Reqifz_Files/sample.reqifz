## HEAD_DCS_001 (Heading)
Door Control System - Safety and Security Features

## INFO_DCS_001 (Information)
The door control system manages automatic locking and unlocking based on vehicle motion, speed, and door state. This system is critical for passenger safety and vehicle security.

## DESIGN_DCS_001 (Design Information)
Door Control ECU Architecture: The system receives inputs from CAN bus (vehicle speed, gear position), door sensors (open/close state), and motion sensors. Primary output controls the door lock actuators via relay drivers.

## PARAM_DCS_001 (Application Parameter)
SPEED_THRESHOLD: 5 km/h - Minimum vehicle speed required for automatic door locking activation

## SIF_DCS_001 (System Interface)
B_VEHICLE_MOVING: Boolean input signal from vehicle motion sensor indicating forward/reverse movement

## SIF_DCS_002 (System Interface)
B_DOOR_OPEN: Boolean input signal from door position sensor (0=closed, 1=open)

## SIF_DCS_003 (System Interface)
B_SPEED_ABOVE_THRESHOLD: Boolean input signal indicating vehicle speed > 5 km/h

## SIF_DCS_004 (System Interface)
B_DOOR_LOCK_CMD: Boolean output command to door lock actuator (1=lock, 0=unlock)

## REQ_DCS_001 (System Requirements)
Automatic Door Lock Control Logic
| No. | Input |  |  | Output |
| --- | --- | --- | --- | --- |
| Test Case | B_VEHICLE_MOVING | B_DOOR_OPEN | B_SPEED_ABOVE_THRESHOLD | B_DOOR_LOCK_CMD |
| 1 | 0 | 0 | 0 | 0 |
| 2 | 0 | 0 | 1 | 0 |
| 3 | 0 | 1 | 0 | 0 |
| 4 | 0 | 1 | 1 | 0 |
| 5 | 1 | 0 | 0 | 0 |
| 6 | 1 | 0 | 1 | 1 |
| 7 | 1 | 1 | 0 | 0 |
| 8 | 1 | 1 | 1 | 0 |

## HEAD_WCS_001 (Heading)
Window Control System - Automatic Rain Response

## SIF_WCS_001 (System Interface)
B_MANUAL_WINDOW_UP: Boolean input from driver window up switch

## SIF_WCS_002 (System Interface)
B_RAIN_DETECTED: Boolean input signal from rain sensor (1=rain detected, 0=no rain)

## SIF_WCS_003 (System Interface)
B_WINDOW_MOTOR_UP: Boolean output command to window motor for upward movement

## REQ_WCS_001 (System Requirements)
Automatic Window Control with Rain Override Logic
| No. | Input |  | Output |
| --- | --- | --- | --- |
| Test Case | B_MANUAL_WINDOW_UP | B_RAIN_DETECTED | B_WINDOW_MOTOR_UP |
| 1 | 0 | 0 | 0 |
| 2 | 0 | 1 | 1 |
| 3 | 1 | 0 | 1 |
| 4 | 1 | 1 | 1 |
